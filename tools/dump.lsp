(defun dmp-w (s) (write-line s *f*))
(defun dmp-inc (key alist / p)
  (if (setq p (assoc key alist))
    (subst (cons key (1+ (cdr p))) p alist)
    (cons (cons key 1) alist)))
(defun c:DUMPDWG (/ out lay blk e ed typ cnt-type cnt-layer cnt-blk texts dims ss i ent attrs a ad lo)
  (setq out (strcat (getvar "DWGPREFIX") "dump.txt"))
  (setq *f* (open out "w"))
  (dmp-w (strcat "EXTMIN " (vl-princ-to-string (getvar "EXTMIN")) " EXTMAX " (vl-princ-to-string (getvar "EXTMAX")) " INSUNITS " (itoa (getvar "INSUNITS")) " DIMSCALE " (rtos (getvar "DIMSCALE"))))
  (dmp-w "=== LAYERS ===")
  (setq lay (tblnext "LAYER" T))
  (while lay (dmp-w (cdr (assoc 2 lay))) (setq lay (tblnext "LAYER")))
  (dmp-w "=== BLOCK DEFS ===")
  (setq blk (tblnext "BLOCK" T))
  (while blk
    (if (not (wcmatch (cdr (assoc 2 blk)) "`**"))
      (progn
        (setq attrs "" e (cdr (assoc -2 blk)))
        (while e
          (setq ed (entget e))
          (if (= (cdr (assoc 0 ed)) "ATTDEF") (setq attrs (strcat attrs " " (cdr (assoc 2 ed)))))
          (setq e (entnext e)))
        (dmp-w (strcat (cdr (assoc 2 blk)) " | attdefs:" attrs))))
    (setq blk (tblnext "BLOCK")))
  (dmp-w "=== LAYOUTS ===")
  (foreach lo (layoutlist) (dmp-w lo))
  (setq e (entnext) cnt-type nil cnt-layer nil cnt-blk nil i 0)
  (while e
    (setq ed (entget e) typ (cdr (assoc 0 ed)))
    (if (not (member typ '("ATTRIB" "SEQEND" "VERTEX")))
      (progn
        (setq cnt-type (dmp-inc (strcat (if (assoc 410 ed) (cdr (assoc 410 ed)) "?") " / " typ) cnt-type))
        (setq cnt-layer (dmp-inc (strcat (cdr (assoc 8 ed)) " / " typ) cnt-layer))
        (cond
          ((= typ "INSERT")
           (setq cnt-blk (dmp-inc (strcat (cdr (assoc 410 ed)) " / " (cdr (assoc 2 ed))) cnt-blk)))
          ((and (member typ '("TEXT" "MTEXT")) (< i 1500))
           (setq i (1+ i))
           (setq texts (cons (strcat (cdr (assoc 410 ed)) " | " (cdr (assoc 8 ed)) " | " (vl-princ-to-string (mapcar '(lambda (x) (fix x)) (cdr (assoc 10 ed)))) " | " (cdr (assoc 1 ed))) texts))))))
    (setq e (entnext e)))
  (dmp-w "=== COUNT BY LAYOUT/TYPE ===")
  (foreach p (reverse cnt-type) (dmp-w (strcat (car p) " = " (itoa (cdr p)))))
  (dmp-w "=== COUNT BY LAYER/TYPE ===")
  (foreach p (reverse cnt-layer) (dmp-w (strcat (car p) " = " (itoa (cdr p)))))
  (dmp-w "=== INSERTS BY LAYOUT/BLOCK ===")
  (foreach p (reverse cnt-blk) (dmp-w (strcat (car p) " = " (itoa (cdr p)))))
  (dmp-w "=== TEXTS ===")
  (foreach t1 (reverse texts) (dmp-w t1))
  (close *f*)
  (princ (strcat "\nDUMP DONE " out))
  (princ))
